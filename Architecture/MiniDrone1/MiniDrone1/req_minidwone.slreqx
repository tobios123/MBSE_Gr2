# req_minidwone

## req_minidwone: References to req_minidwone.docx (Container)
Read-only references to Microsoft Word document.

### Takeoff and Land (Functional)
Takeoff and Land
The minidrone must have Vertical takeoff and landing (VTOL) capabilities. This will enable the minidrone to have
· efficient maneuverability
· ability to hover steadily
· minimal space needed to launch

### Perform Controlled Flight (Functional)
Perform Controlled Flight
The minidrone should have a 6 DOF movement capability during flight to achieve its desired applications.

#### Flight Region (Functional)
Flight Region
To avoid expected obstacles in its operation area, the drone must be able to achieve and maintain a constant altitude of 2 meters.

#### Flight Control (Functional)
Flight Control
The flight is managed from a control system, and it can operate autonomously or based on guidance from central location

### Communicate with Ground base (Functional)
Communicate with Ground base
The minidrone should be able to receive commands and send information to a ground base that controls its operation.

#### Camera (Functional)
Camera
The minidrone must be able to snap a picture of the package.

### Carry a load (Functional)
Carry a load
The minidrone should be able to carry a load

#### Max size (Functional)
Max size
Max size of 5x5x5 cm

#### Max weight (Functional)
Max weight
Max weight of 500 grams

#### Grap controller (Functional)
Grap controller
In order to grap the packages the drone should have a grapper to pick up and deliver the package

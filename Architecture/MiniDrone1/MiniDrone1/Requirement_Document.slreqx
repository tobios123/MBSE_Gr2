# Requirement_Document

## Requirement Document: References to Requirement Document.docx (Container)
Read-only references to Microsoft Word document.

### General Information (Functional)
General Information
This SRS document described the requirements for the development of a minidrone . This multi-purpose drone is a rotary-wing flying object whose development and application range is expanding in the last decade.
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
### Functionalities (Functional)
Functionalities
The minidrone should be able to support different applications in Agriculture, Logistics and delivery, Emergency response, Inspection. To offer functionality in such broad range of applications the minidrone need to satisfy the following basic functional requirements

#### Takeoff and Land (Functional)
Takeoff and Land
The minidrone must have Vertical takeoff and landing (VTOL) capabilities. This will enable the minidrone to have
· efficient maneuverability
· ability to hover steadily
· minimal space needed to launch

#### Perform Controlled Flight (Functional)
Perform Controlled Flight
The minidrone should have a 6 DOF movement capability during flight to achieve its desired applications.

##### Flight Region (Functional)
Flight Range
The range of the minidrone must be at least 20 kilometers. This will extend the usability of the minidrone by allowing longer range o

##### Flight Control (Functional)
f operation and reach.
Flight Region
To avoid expected obstacles in its operation area, the drone must be able to achieve and maintain

#### Communicate with Ground base (Functional)
a constant altitude of 200 meters.
Flight Control
The flight is managed from a control system, and it can operate autonomously or based on guida

##### Camera (Functional)
nce from central location
Carry a load
The minidrone should be able to carry a maximum load of 5 kg.
Communicate with Ground base
The minidrone should be able to receive comm

### Project proposal group 2 (Functional)
ds and send information to a ground base that controls its operation
System Components
An operation mini drone should have the following basic components
- Main Body
- Power Module
- Propulsion Module
- Flight Control Module
- Sensor Module
- Communication Module
- Payload
Main Body
The is the central hub provides structural support and housing for the other components making up the minidrone. It also contains connection point to attach the payload to the minidrone.
Power Module
The power unit should be able to provide necessary power to the propulsion, flight control and communication modules.
Propulsion Module
The propulsion module consists of one or more rotor assemblies that contain a propeller and a motor driving the propeller.
Flight Control Module
The flight control module consists of the following basic components
- Control System
- Path Planning
Control Sy

### “System Components (Functional)
stem
Flight controller receives data from sensors and performs calculations, designed in control strategy to control the behavior of the vehicle while performing different maneuvers
Path plann

#### Main Body (Functional)
ing
The system should plan its original path and continuously update it based on environmental factors or new user requests
Sensor Module
The minidrone should have a redundant IMU for improved cali

#### Power Module (Functional)
bration and pose estimation. It also contains encoder sensors to measure velocity of propeller motors for use as an input to the fl

#### Propulsion Module (Functional)
ight control modules.
Communication Module
The minidrone must have Wi-Fi network communication and radio communication.
Payload
The minidrone

#### Flight Control Module (Functional)
can carry different payload types depending on the application focus. A camera is the most often used payload to deliver

##### Control System (Functional)
images and video to a central control location.

##### Path planning (Functional)

#### Sensor Module (Functional)

#### Communication Module (Functional)

#### Payload (Functional)
